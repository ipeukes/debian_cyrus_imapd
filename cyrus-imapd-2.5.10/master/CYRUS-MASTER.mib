CYRUS-MASTER-MIB DEFINITIONS ::= BEGIN

IMPORTS
    MODULE-IDENTITY, OBJECT-TYPE, Counter32, enterprises
        FROM SNMPv2-SMI
    DisplayString
        FROM SNMPv2-TC;
--    cmuCyrus
--        FROM CMU-MIB;

cmuMIB         OBJECT IDENTIFIER ::= { enterprises 3 }
cmuCyrus       OBJECT IDENTIFIER ::= { cmuMIB 6 }

cyrusMasterMIB MODULE-IDENTITY
    LAST-UPDATED "0010312300Z"		-- 2000 Oct 31
    ORGANIZATION "CMU Project Cyrus"
    CONTACT-INFO
                "       Email: cyrus-bugs@andrew.cmu.edu

		        Project Cyrus
                        Computing Services
                        Carnegie Mellon University
                        Pittsburgh PA. 15213
                "
    DESCRIPTION "A simple MIB for application status of the Cyrus
	         master process.
		"
	::= { cmuCyrus 1 }
           -- cmuCyrus = .1.3.6.1.4.1.3.6
           -- cyrusMasterMIB = .1.3.6.1.4.1.3.6.1

-- general information

cyrusMasterInfo OBJECT IDENTIFIER ::= { cyrusMasterMIB 1 }

  -- version information

   cyrusMasterInfoDescr  OBJECT-TYPE 

                         SYNTAX     DisplayString (SIZE (0..255)) 

                         ACCESS     read-only 

                         STATUS     mandatory 

                         DESCRIPTION   "A general textual description 

                                        of the Cyrus server." 

                         ::= { cyrusMasterInfo 1 }

   cyrusMasterInfoVers   OBJECT-TYPE 

                         SYNTAX     DisplayString (SIZE (0..255)) 

                         ACCESS     read-only 

                         STATUS     mandatory 

                         DESCRIPTION  "The version of the Cyrus server."

                         ::= { cyrusMasterInfo 2 } 

   cyrusMasterInfoUptime OBJECT-TYPE

                         SYNTAX	    TimeTicks

			 ACCESS	    read-only
			 
			 STATUS	    current

			 DESCRIPTION "The amount of time since the master
			              process was last started."

			 ::= { cyrusMasterInfo 3 }

   -- service table

   serviceTable          OBJECT-TYPE 

                         SYNTAX     SEQUENCE OF serviceEntry

                         ACCESS     not-accessible 

                         STATUS     mandatory 

                         ::= { cyrusMasterMIB 2 }


   serviceEntry          OBJECT-TYPE 

                         SYNTAX     ServiceEntry 

                         ACCESS     not-accessible 

                         STATUS     mandatory 

                         INDEX     { serviceId } 

                         ::= { serviceTable 1 } 


   ServiceEntry      ::= SEQUENCE { 

                         serviceForks		Counter32,

			 serviceActive		Gauge32,

			 serviceName		DisplayString (SIZE (0..255)),

			 serviceId		INTEGER,

                         serviceConnections     Counter32

                         } 		   

      -- forks since startup
      serviceForks       OBJECT-TYPE 

                         SYNTAX     Counter32 

                         ACCESS     read-only 

                         STATUS     mandatory 

                         DESCRIPTION  "The total number of forks for this 
			               service since initialization." 

                         ::= { serviceEntry 1 } 

             

      -- active children
      serviceActive      OBJECT-TYPE 

                         SYNTAX     Gauge32 

                         ACCESS     read-only 

                         STATUS     mandatory 

                         DESCRIPTION  "The total number of children currently 

                                       active." 

                         ::= { serviceEntry 2 } 


      serviceName        OBJECT-TYPE 

                         SYNTAX     DisplayString (SIZE (0..255))

                         ACCESS     read-only 

                         STATUS     mandatory 

                         DESCRIPTION  "The name of this service."

                         ::= { serviceEntry 3 } 

      serviceId          OBJECT-TYPE 

                         SYNTAX     INTEGER 

                         ACCESS     not-accessible

                         STATUS     mandatory 

                         DESCRIPTION  "The id of the service as configured." 

                         ::= { serviceEntry 4 }

      -- connections since startup
      serviceConnections  OBJECT-TYPE 

                         SYNTAX     Counter32 

                         ACCESS     read-only 

                         STATUS     mandatory 

                         DESCRIPTION  "The total number of connections for this 
			               service since initialization." 

                         ::= { serviceEntry 5 } 

-- event table

--   eventTable            OBJECT-TYPE 
--                         SYNTAX     SEQUENCE OF eventEntry
--                         ACCESS     not-accessible 
--                         STATUS     mandatory 
--                         ::= { cyrusMasterMIB 3 }

END
